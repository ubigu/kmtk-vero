FME workspace kmtk_vero_fme_workbench.fmw

Parameters:
- DestDataset_SHAPE =
- DestDataset_SHAPEFILE_11 =
- DestDataset_SHAPEFILE_12 =
- DestDataset_SHAPEFILE_13 =
- DestDataset_SHAPEFILE_14 =
- DestDataset_SHAPEFILE_15 =
- DestDataset_SHAPEFILE_16 =
- FEATURE_TYPES =
- FEATURE_TYPES_2 =
- FEATURE_TYPES_3 =
- FEATURE_TYPES_4 =
- SourceDataset_CSV2 =
- SourceDataset_OGCAPI_FEATURES =
- SourceDataset_OGCAPI_FEATURES_4 =
- SourceDataset_OGCAPI_FEATURES_5 =
- SourceDataset_OGCGEOPACKAGE =
- SourceDataset_SHAPEFILE_4 =
- SourceDataset_XLSXR =
- SourceDataset_XLSXR_5 =

Readers:
- OGCAPI_FEATURES_1: OGCAPI_FEATURES from $(SourceDataset_OGCAPI_FEATURES)
- OGCAPI_FEATURES_2: OGCAPI_FEATURES from $(SourceDataset_OGCAPI_FEATURES_5)
- XLSXR_1: XLSXR from $(SourceDataset_XLSXR)
- XLSXR_2: XLSXR from $(SourceDataset_XLSXR_5)
- OGCGEOPACKAGE_1: OGCGEOPACKAGE from $(SourceDataset_OGCGEOPACKAGE) in EPSG:3067
- OGCAPI_FEATURES_3: OGCAPI_FEATURES from $(SourceDataset_OGCAPI_FEATURES_4)
- CSV2_1: CSV2 from $(SourceDataset_CSV2) in ETRS89.FinGK-25/10_FME
- SHAPEFILE_2: SHAPEFILE from $(SourceDataset_SHAPEFILE_4)

Writers:
- SHAPE_1: SHAPE to $(DestDataset_SHAPE)
- SHAPEFILE_3: SHAPEFILE to $(DestDataset_SHAPEFILE_11)
- SHAPEFILE_4: SHAPEFILE to $(DestDataset_SHAPEFILE_14) in EPSG:3067
- SHAPEFILE_5: SHAPEFILE to $(DestDataset_SHAPEFILE_12) in EPSG:3067
- SHAPEFILE_6: SHAPEFILE to $(DestDataset_SHAPEFILE_16) in EPSG:3067
- SHAPEFILE_7: SHAPEFILE to $(DestDataset_SHAPEFILE_13) in EPSG:3067
- SHAPEFILE_8: SHAPEFILE to $(DestDataset_SHAPEFILE_15) in EPSG:3067

Note: Lisää OGC-API kyselyihin authkey
kunta (reader OGCAPI_FEATURES_3)
    attributes: id int64, mtk_id int64, sijaintitarkkuus int64, aineistolahde int64, alkupvm buffer, kohderyhma int64, kohdeluokka int64, kuntatunnus int64, sijainti_piste.type buffer, sijainti_piste.coordinates{} real64
    -> Reprojector_3
Reprojector_3
    DEST = EPSG:3067
    INTERPOLATION_TYPE_NAME = Nearest Neighbor
    RASTER_CELL_SIZE = Preserve Cells
    RASTER_TOLERANCE = 0.0
    SOURCE = EPSG:4326
    REPROJECTED -> TestFilter_12
TestFilter_12
    DEFAULT_VALUE = <UNFILTERED>
    TEST_LIST = "BOOL_OP,OR,COMPOSITE_TEST,""""""1"""""",TEST_CLAUSE,TEST @Value(kuntatunnus) = 905",905
    905 -> SpatialFilter_6 [Filter]
TestFilter_13
    DEFAULT_VALUE = <UNFILTERED>
    TEST_LIST = "BOOL_OP,OR,COMPOSITE_TEST,""""""1"""""",TEST_CLAUSE,TEST @Value(col0) = 01.01.02.17",@Value(col0) = 01.01.02.17,"BOOL_OP,OR,COMPOSITE_TEST,""""""1"""""",TEST_CLAUSE,TEST @Value(col0) = 12.06.01.19",@Value(col0) = 12.06.01.19,"BOOL_OP,OR,COMPOSITE_TEST,""""""1"""""",TEST_CLAUSE,TEST @Value(col0) = 12.07.01.19",@Value(col0) = 12.07.01.19,"BOOL_OP,OR,COMPOSITE_TEST,""""""1"""""",TEST_CLAUSE,TEST @Value(col0) = 12.08.01.19",@Value(col0) = 12.08.01.19,"BOOL_OP,OR,COMPOSITE_TEST,""""""1"""""",TEST_CLAUSE,TEST @Value(col0) = 12.09.01.19",@Value(col0) = 12.09.01.19,"BOOL_OP,OR,COMPOSITE_TEST,""""""1"""""",TEST_CLAUSE,TEST @Value(col0) = 12.10.01.19",@Value(col0) = 12.10.01.19,"BOOL_OP,OR,COMPOSITE_TEST,""""""1"""""",TEST_CLAUSE,TEST @Value(col0) = 12.11.01.19",@Value(col0) = 12.11.01.19,"BOOL_OP,OR,COMPOSITE_TEST,""""""1"""""",TEST_CLAUSE,TEST @Value(col0) = 12.11.01.19",@Value(col0) = 12.11.01.19
    @Value(col0) = 01.01.02.17 -> AttributeRenamer
    @Value(col0) = 12.06.01.19 -> AttributeRenamer_2
    @Value(col0) = 12.07.01.19 -> AttributeRenamer_3
    @Value(col0) = 12.08.01.19 -> AttributeRenamer_4
    @Value(col0) = 12.09.01.19 -> AttributeRenamer_5
    @Value(col0) = 12.10.01.19 -> AttributeRenamer_6
    @Value(col0) = 12.11.01.19 -> AttributeRenamer_7
AttributeExposer
    ATTR_LIST = kiinteistotunnus
    -> TestFilter_3
TestFilter_3
    DEFAULT_VALUE = <UNFILTERED>
    TEST_LIST = "BOOL_OP,OR,COMPOSITE_TEST,""""""1"""""",TEST_CLAUSE,CASE_INSENSITIVE_TEST @Value(kiinteistotunnus) BEGINS_WITH 905",905
    905 -> Reprojector
Reprojector
    DEST = EPSG:3067
    INTERPOLATION_TYPE_NAME = Nearest Neighbor
    RASTER_CELL_SIZE = Preserve Cells
    RASTER_TOLERANCE = 0.0
    SOURCE = EPSG:4326
    REPROJECTED -> KTJ_PALSTAN_SIJAINTITIEDOT
    REPROJECTED -> SpatialFilter_2 [Filter]
Note: Lisää kunnan VTJ-PRT-analyysidata
analyysi (reader XLSXR_1)
    attributes: Tn char(3), Id number(11,0), XI number(10,3), YP number(11,3), Kä char(48), Pa number(5,0), Ke char(11), VTJPRT char(11), VTJXI number(10,3), VTJXP number(11,3), VTJKä char(69), VTJPa number(5,0), VTJKe number(2,0), T1 number(2,0), T2 string, T3 string, T4 string, T5 string, T6 string, Käv char(1), Pav string, Kev string
    -> TestFilter_5
TestFilter_5
    DEFAULT_VALUE = <UNFILTERED>
    TEST_LIST = "BOOL_OP,OR,COMPOSITE_TEST,""""""1"""""",TEST_CLAUSE,TEST XI ATTRIBUTE_HAS_A_VALUE """,loytyy_koordinaatit
    loytyy_koordinaatit -> VertexCreator
    <UNFILTERED> -> TestFilter_6
TestFilter_6
    DEFAULT_VALUE = <UNFILTERED>
    TEST_LIST = "BOOL_OP,OR,COMPOSITE_TEST,""""""1"""""",TEST_CLAUSE,TEST VTJXI ATTRIBUTE_HAS_A_VALUE """,loytyy_koordinaatit
    loytyy_koordinaatit -> VertexCreator_2
Note: Kunnan VTJ-rakennustiedot xls-muodossa
R1 rakennus (reader XLSXR_2)
    attributes: Rakennustunnus char(11), Sijainti-kunta number(4,0), Raken-nuksen tila number(3,0), Muutos-laji char(3), Alkupäivä date, Loppupäivä date, Voi-massa-olo number(2,0), Lisäyspäivä date, Sijaintikiinteistön tunnus number(15,0), Kiinteistöyksikön nimi char(24), Muuttuvan rak.tunnuksen kiinteistötunnus number(15,0), Tarkis-tus-merkki char(2), Raken-nus-numero number(4,0), Kiinteistöyksikön määräalan tunnus string, Posti-numero number(6,0), Valmistumis-_päivä date, Rak.luvan valmistu-mispäivä date, Poik-keus-_lupa number(2,0), Tieto-lähde number(2,0), Perus-parannus number(2,0), Perus-parannus-päivä date, Kaava number(2,0), Hallinta-peruste number(2,0), Julkisivu-materi-aali number(2,0), Kerros-ala number(5,0), Kerrosalan muutospäivä date, Kerros-luku number(2,0), Kerrosluvun muutospäivä date, Koko-naisala number(5,0), Kokonais-alan muutospäivä date,
      Huo-neisto-ala string, Huoneisto-alan muutospäivä string, Tilavuus number(6,0), Tilavuuden muutospäivä date, Kellari-ala number(5,0), Käytös-säolo-tilanne number(3,0), Käytössä-olotilanteen muutospäivä date, Käyttö-tarkoitus number(4,0), Käyttö-tarkoituksen muutospäivä date, Lämmi-tystapa number(2,0), Lämmitys-tavan muutospäivä date, Poltto-aine number(3,0), Polttoaineen muutospäivä date, Raken-nusma-teriaali number(2,0), Rungon raken-nustapa number(2,0), Varusteiden muutospäivä date, Sähkö number(2,0), Kaasu number(2,0), Viemäri number(2,0), Vesijohto number(2,0), Lämmin vesi number(2,0), Aurinko-paneeli number(2,0), Hissi number(2,0), Ilmas-tointi number(2,0), Saunojen luku-määrä number(2,0), Väestö-suoja-koko number(3,0), Verkosto-liittymien muutospäivä date, Viemäri-liittymä number(2,0), Vesi-johto-liittymä number(2,0), Sähkö-liittymä number(2,0),
      Kaasu-liittymä string, Kaapeli-liittymä number(2,0), Pohjois-koordinaatti number(8,0), Itä-koordinaatti number(7,0), Koordi-naatti-varmuus char(2), Asumis-oikeus-tyyppi string, Äänestys-alueen kunta number(4,0), Äänestys-alue number(5,0), Tuleva kunta-numero number(4,0), Tuleva äänestys-alue number(5,0), Käyttötark_tietolähde char(9), Rakennus-_luokka number(5,0), Rakennus-_luokan muutospäivä date, Rakennnus-_luokka_tietolähde char(20)
    -> TestFilter_2
TestFilter_2
    DEFAULT_VALUE = <UNFILTERED>
    TEST_LIST = "BOOL_OP,OR,COMPOSITE_TEST,""""""1"""""",TEST_CLAUSE,TEST Pohjois-koordinaatti ATTRIBUTE_HAS_A_VALUE """,loytyy_koordinaatit
    loytyy_koordinaatit -> VertexCreator_3
VertexCreator_3
    MEASURE_TYPE = Continuous
    MISSING_VAL_MODE = Compute
    MODE_NAME = Add Point
    XVAL = @Value(Itä-koordinaatti)
    YVAL = @Value(Pohjois-koordinaatti)
    -> TestFilter_15
TestFilter_15
    DEFAULT_VALUE = <UNFILTERED>
    TEST_LIST = "BOOL_OP,OR,COMPOSITE_TEST,""""""1"""""",TEST_CLAUSE,TEST @Value(Voi-massa-olo) = 1",voimassa
    voimassa -> TestFilter_26
TestFilter_26
    DEFAULT_VALUE = <UNFILTERED>
    TEST_LIST = "BOOL_OP,OR,COMPOSITE_TEST,""""""1"""""",TEST_CLAUSE,TEST Rakennustunnus ATTRIBUTE_IS_MISSING """,missing
    <UNFILTERED> -> FeatureMerger_18 [SUPPLIER]
    <UNFILTERED> -> FeatureMerger_26 [REQUESTOR]
    <UNFILTERED> -> Bufferer_2
Bufferer_2
    ANGLE = 22.5
    CAP_STYLE = Arc
    CORNER_STYLE = Arc
    MODE = AREA
    OFFSET = 1
    OFFSET_UNITS = NONE
    PRECISION = APPROX
    BUFFERED -> SpatialFilter_3 [Filter]
    BUFFERED -> METRIN_BUFFER (writer SHAPEFILE_4)
METRIN_BUFFER (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20)
R1 rakennus/Ratu_R1 (reader XLSXR_2) [off]
    attributes: Rakennustunnus char(11)
Note: Lisää OGC-API kyselyihin authkey
buildings (reader OGCAPI_FEATURES_1)
    attributes: id buffer, featureClass buffer, kmtkId buffer, version int64, VTJprt buffer, sourceId buffer, PNRplaceId buffer, startTime buffer, versionStartTime buffer, versionEndTime buffer, endTime buffer, dataSource int64, sourceModificationTime buffer, state int64, verificationDate buffer, updateReason buffer, lifecycleStatus int64, constructionDate buffer, modificationDate buffer, demolitionDate buffer, function buffer, area buffer, floorArea buffer, volume buffer, heightAbsolute real64, heightAbsoluteAccuracy buffer, heightRelative buffer, floors buffer, floorsAboveGround buffer, relationToGround int64,
      isFlightObstacle buffer, hasElevator buffer, isConnectedToGas buffer, isConnectedToElectricity buffer, isConnectedToWater buffer, isConnectedToSewage buffer, heatingType buffer, heatingFuel buffer, numberOfParts int64, attributeDataSource int64
    -> Reprojector_2
Reprojector_2
    DEST = EPSG:3067
    INTERPOLATION_TYPE_NAME = Nearest Neighbor
    RASTER_CELL_SIZE = Preserve Cells
    RASTER_TOLERANCE = 0.0
    SOURCE = EPSG:4326
    REPROJECTED -> SpatialFilter_6 [Candidate]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter [Filter]
    PASSED -> TAMA
TAMA: Inspector
Note: LISÄÄ TÄHÄN ALKUUN KUNTAREKISTERIN READER
Note: Rakennusten käsittely: Luparakennuksista mukaan vain ne uniikit, joita ei mukana ei luparakennuksissa, tupla ID:t poistetaan, rakennusnumeroista poistetaan etunollat ja missing PRT:t myös mukaan jne...
Reprojector_4
    DEST = EPSG:3067
    INTERPOLATION_TYPE_NAME = Nearest Neighbor
    RASTER_CELL_SIZE = Preserve Cells
    RASTER_TOLERANCE = 0.0
    SOURCE = EPSG:3876
    REPROJECTED -> TestFilter_16
    REPROJECTED -> TestFilter_20
TestFilter_20
    DEFAULT_VALUE = <UNFILTERED>
    TEST_LIST = "BOOL_OP,OR,COMPOSITE_TEST,""""""1"""""",TEST_CLAUSE,TEST @Value(BUILDINGRE) = 2",lupavaiheen_rakennukset
    lupavaiheen_rakennukset -> TestFilter_21
    <UNFILTERED> -> DuplicateFilter_2
TestFilter_21
    DEFAULT_VALUE = <UNFILTERED>
    TEST_LIST = "BOOL_OP,OR,COMPOSITE_TEST,""""""1"""""",TEST_CLAUSE,TEST @Value(PERMANENTB) = """,PERMANENTBUILDINGLABEL
    <UNFILTERED> -> DuplicateFilter_2
DuplicateFilter_2
    INPUT_ORDERED_CHOICE = No
    KEYATTR = ID
    UNIQUE -> DuplicateFilter_3
DuplicateFilter_3
    INPUT_ORDERED_CHOICE = No
    KEYATTR = PERMANENTB
    UNIQUE -> AttributeTrimmer_2
    DUPLICATE -> TestFilter_29
TestFilter_29
    DEFAULT_VALUE = <UNFILTERED>
    TEST_LIST = "BOOL_OP,OR,COMPOSITE_TEST,""""""1"""""",TEST_CLAUSE,TEST PERMANENTB ATTRIBUTE_IS_MISSING """,missing
    missing -> AttributeTrimmer_2
AttributeTrimmer_2
    SRC_ATTRS = BUILDINGNU
    TRIM_CHARS = 0
    TRIM_TO_NONE = No
    TRIM_TYPE = Left
    -> FeatureMerger_18 [REQUESTOR]
    -> SpatialFilter_3 [Candidate]
    -> FeatureMerger [REQUESTOR] [off]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> KUNTA-VTJ_-_SIJAINNILLA_LINKITETTY_ILMAN_TUNNUS_LINKITYSTA (writer SHAPEFILE_4)
    FAILED -> KUNTA-VTJ_-_SIJAINNILLA_EI_LINKITTYNEET_ILMAN_TUNNUS_LINKITYSTA (writer SHAPEFILE_4)
KUNTA-VTJ_-_SIJAINNILLA_LINKITETTY_ILMAN_TUNNUS_LINKITYSTA (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), _predicate char(254)
KUNTA-VTJ_-_SIJAINNILLA_EI_LINKITTYNEET_ILMAN_TUNNUS_LINKITYSTA (writer SHAPEFILE_4)
Bufferer
    ANGLE = 22.5
    CAP_STYLE = Arc
    CORNER_STYLE = Arc
    MODE = AREA
    OFFSET = 1
    OFFSET_UNITS = NONE
    PRECISION = APPROX
    BUFFERED -> SpatialFilter_8 [Filter]
    BUFFERED -> SpatialFilter_9 [Filter]
    BUFFERED -> Bufferer_Buffered
TestFilter_24
    DEFAULT_VALUE = <UNFILTERED>
    TEST_LIST = "BOOL_OP,OR,COMPOSITE_TEST,""""""1"""""",TEST_CLAUSE,TEST Rakennustunnus ATTRIBUTE_IS_MISSING """,missing
    <UNFILTERED> -> FeatureMerger_23 [REQUESTOR]
TestFilter
    DEFAULT_VALUE = <UNFILTERED>
    TEST_LIST = "BOOL_OP,OR,COMPOSITE_TEST,""""""1"""""",TEST_CLAUSE,CASE_INSENSITIVE_TEST T5 ATTRIBUTE_HAS_A_VALUE """,T5,"BOOL_OP,OR,COMPOSITE_TEST,""""""1"""""",TEST_CLAUSE,TEST T6 ATTRIBUTE_HAS_A_VALUE """,T6
    T5 -> VertexCreator [off]
    T6 -> VertexCreator_2 [off]
    <UNFILTERED> -> VertexCreator [off]
VertexCreator
    MEASURE_TYPE = Continuous
    MISSING_VAL_MODE = Compute
    MODE_NAME = Add Point
    XVAL = @Value(XI)
    YVAL = @Value(YP)
    -> SpatialFilter_2 [Candidate]
    -> SpatialFilter [Candidate] [off]
VertexCreator_2
    MEASURE_TYPE = Continuous
    MISSING_VAL_MODE = Compute
    MODE_NAME = Add Point
    XVAL = @Value(VTJXI)
    YVAL = @Value(VTJXP)
    -> SpatialFilter_2 [Candidate]
    -> SpatialFilter [Candidate] [off]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> TestFilter_25
TestFilter_25
    DEFAULT_VALUE = <UNFILTERED>
    TEST_LIST = "BOOL_OP,OR,COMPOSITE_TEST,""""""1"""""",TEST_CLAUSE,TEST VTJPRT ATTRIBUTE_IS_MISSING """,missing
    <UNFILTERED> -> FeatureMerger_23 [SUPPLIER]
    <UNFILTERED> -> FeatureMerger_2 [SUPPLIER]
    <UNFILTERED> -> FeatureMerger [SUPPLIER]
VTJ-PRT-ANALYYSI_T1-T4_T6_KUNTAREK_VTJPRT_LINKITYS (writer SHAPEFILE_5)
    attributes: id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69), VTJPa number(5,0), VTJKe number(2,0), T1 number(2,0), T2 char(254), T3 char(254), T4 char(254), T5 char(254), T6 char(254), Käv char(1), Pav char(254), Kev char(254), _predicate char(254)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_Passed
    FAILED -> SpatialFilter_Failed
SpatialFilter_Passed: Inspector
SpatialFilter_Failed: Inspector
VEROANALYYSI_VTJ-PRT-ANALYYSI_MUUTTUVALLA_RAKENNUSTUNNUKSELLA_LINKITTYVÄT: Inspector

Bookmark: Lähdetiedosto
CSV (reader CSV2_1)
    attributes: col0 string, col1 string, col2 uint32, col3 string, col4 string, col5 string, col6 string, col7 real32, col8 string, col9 string, col10 string, col11 real64, col12 uint32, col13 uint32, col14 string, col15 uint8, col16 uint8, col17 real64, col18 real64, col19 uint8, col20 uint8, col21 string, col22 uint16, col23 uint8, col24 uint8, col25 uint8, col26 uint8, col27 uint16, col28 uint16, col29 string,
      col30 string, col31 string, col32 uint8, col33 uint8, col34 uint8
    -> TestFilter_13

Bookmark: Kenttien nimet Excelistä
AttributeRenamer
    ATTR_TABLE:
      RENAME_SET_DEFAULT col0 > Tietotyyppi
      RENAME_SET_DEFAULT col1 > Tietuetunnus
      RENAME_SET_DEFAULT col2 > Ajopäivä
      RENAME_SET_DEFAULT col3 > Verovuosi
      RENAME_SET_DEFAULT col4 > Tietueiden määrä yhteensä
AttributeRenamer_2
    ATTR_TABLE:
      RENAME_SET_DEFAULT col0 > Tietuetunnus
      RENAME_SET_DEFAULT col1 > Kiinteistötunnus
      RENAME_SET_DEFAULT col2 > Kiinteistön sijaintikunnan numero
      RENAME_SET_DEFAULT col3 > Sijaintikunnan nimi
      RENAME_SET_DEFAULT col4 > Kiinteistön nimi
      RENAME_SET_DEFAULT col5 > Kiinteistön kokonaispinta-ala (m2)
      RENAME_SET_DEFAULT col6 > Kiinteistöverotuksen päättymispäivä
      RENAME_SET_DEFAULT col7 > Verotuksen oikaisun päätöspäivä
AttributeRenamer_3
    ATTR_TABLE:
      RENAME_SET_DEFAULT col0 > Tietuetunnus
      RENAME_SET_DEFAULT col1 > Kiinteistötunnus
      RENAME_SET_DEFAULT col2 > Maapohjan numero
      RENAME_SET_DEFAULT col3 > Rakennusnumero
      RENAME_SET_DEFAULT col4 > Muun profiilin numero
      RENAME_SET_DEFAULT col5 > Asiakastunnus
      RENAME_SET_DEFAULT col6 > Asiakkaan nimi
      RENAME_SET_DEFAULT col7 > Omistusosuus (osoittaja)
      RENAME_SET_DEFAULT col8 > Omistusosuus (nimittäjä)
      RENAME_SET_DEFAULT col9 > Hallintaosuus (osoittaja)
      RENAME_SET_DEFAULT col10 > Hallintaosuus (nimittäjä)
      RENAME_SET_DEFAULT col11 > Muu hallinta oikeus
AttributeRenamer_4
    ATTR_TABLE:
      RENAME_SET_DEFAULT col0 > Tietuetunnus
      RENAME_SET_DEFAULT col1 > Kiinteistötunnus
      RENAME_SET_DEFAULT col2 > Maapohjan numero
      RENAME_SET_DEFAULT col3 > Maapohjan tyyppi
      RENAME_SET_DEFAULT col4 > Maapohjan käyttötarkoitus
      RENAME_SET_DEFAULT col5 > Maapohjan pinta-ala (m2)
      RENAME_SET_DEFAULT col6 > Rakennusoikeus (k-m2)
      RENAME_SET_DEFAULT col7 > Tonttitehokkuus
      RENAME_SET_DEFAULT col8 > Kaavan laji
      RENAME_SET_DEFAULT col9 > Kaavan mukainen käyttötarkoitus
      RENAME_SET_DEFAULT col10 > Ranta
      RENAME_SET_DEFAULT col11 > Kaavayksikkötunnus
      RENAME_SET_DEFAULT col12 > Laskentaperuste
      RENAME_SET_DEFAULT col13 > Hinta-aluetunnus
      RENAME_SET_DEFAULT col14 > Aluehinta
      RENAME_SET_DEFAULT col15 > Alennuskaava
      RENAME_SET_DEFAULT col16 > Ei kiinteistöveroa
      RENAME_SET_DEFAULT col17 > Verotusarvo
      RENAME_SET_DEFAULT col18 > Kiinteistövero
AttributeRenamer_5
    ATTR_TABLE:
      RENAME_SET_DEFAULT col0 > Tietuetunnus
      RENAME_SET_DEFAULT col1 > Kiinteistötunnus
      RENAME_SET_DEFAULT col2 > Rakennuksen numero
      RENAME_SET_DEFAULT col3 > Pysyvä rakennusnumero
      RENAME_SET_DEFAULT col4 > VRK-rakennustyyppi
      RENAME_SET_DEFAULT col5 > Käyttötarkoitus
      RENAME_SET_DEFAULT col6 > Purkukuntoinen
      RENAME_SET_DEFAULT col7 > Käyttökelvoton
      RENAME_SET_DEFAULT col8 > Ei kiinteistöveroa
      RENAME_SET_DEFAULT col9 > Yleishyödyllisessä käytössä
      RENAME_SET_DEFAULT col10 > Rakennuksen verotusarvo
      RENAME_SET_DEFAULT col11 > Rakennuksen kiinteistövero
    -> FeatureMerger_4 [SUPPLIER]
AttributeRenamer_6
    ATTR_TABLE:
      RENAME_SET_DEFAULT col0 > Tietuetunnus
      RENAME_SET_DEFAULT col1 > Kiinteistötunnus
      RENAME_SET_DEFAULT col2 > Rakennuksen numero
      RENAME_SET_DEFAULT col3 > Rakennuksen osan numero
      RENAME_SET_DEFAULT col4 > Rakennustyyppi
      RENAME_SET_DEFAULT col5 > Rakentamisen alkupäivä
      RENAME_SET_DEFAULT col6 > Valmistumispäivä
      RENAME_SET_DEFAULT col7 > Rakennuksen osan kokonaispinta-ala (m2)
      RENAME_SET_DEFAULT col8 > Rakennuksen osan tilavuus (m3)
      RENAME_SET_DEFAULT col9 > Kantava rakenne
      RENAME_SET_DEFAULT col10 > Peruskorjausvuosi
      RENAME_SET_DEFAULT col11 > Ikäalennusten laskentavuosi
      RENAME_SET_DEFAULT col12 > Viimeistelemättömän kellarin pinta-ala (m2)
      RENAME_SET_DEFAULT col13 > Sähkö
      RENAME_SET_DEFAULT col14 > Lämmitys
      RENAME_SET_DEFAULT col15 > Vesijohto
      RENAME_SET_DEFAULT col16 > Viemäri
      RENAME_SET_DEFAULT col17 > Talviasuttava
      RENAME_SET_DEFAULT col18 > Kuistin pinta-ala (m2)
      RENAME_SET_DEFAULT col19 > WC
      RENAME_SET_DEFAULT col20 > Sauna
      RENAME_SET_DEFAULT col21 > Rakennuksen muoto
      RENAME_SET_DEFAULT col22 > Varastotilojen pinta-ala (m2)
      RENAME_SET_DEFAULT col23 > Hissi
      RENAME_SET_DEFAULT col24 > Hissikuilujen pinta-ala (m2)
      RENAME_SET_DEFAULT col25 > Ilmastointi
      RENAME_SET_DEFAULT col26 > Lämmitys ja vesi
      RENAME_SET_DEFAULT col27 > Kellaritilojen pinta-ala (m2)
      RENAME_SET_DEFAULT col28 > Paikoitusalueen pinta-ala (m2)
      RENAME_SET_DEFAULT col29 > Siilotyyppi
      RENAME_SET_DEFAULT col30 > Siilon halkaisija (m)
      RENAME_SET_DEFAULT col31 > Kasvihuoneen rakenne ja lämmitys
      RENAME_SET_DEFAULT col32 > Kevytrakenteinen ruokala
      RENAME_SET_DEFAULT col33 > Pysäköintitalon ylin kerros katettu
      RENAME_SET_DEFAULT col34 > Lämpöeristys
    -> Sorter
AttributeRenamer_7
    ATTR_TABLE:
      RENAME_SET_DEFAULT col0 > Tietuetunnus
      RENAME_SET_DEFAULT col1 > Kiinteistötunnus
      RENAME_SET_DEFAULT col2 > Muun profiilin numero
      RENAME_SET_DEFAULT col3 > Muun profiilin tyyppi
      RENAME_SET_DEFAULT col4 > Vesivoiman arvo
      RENAME_SET_DEFAULT col5 > Verotusarvo
      RENAME_SET_DEFAULT col6 > Kiinteistövero

Bookmark: Rakennukset&rakennuksen osat
Sorter
    SORT_PARM = "Rakennuksen osan numero" NUMERIC ASCENDING
    SORTED -> DuplicateFilter
DuplicateFilter
    INPUT_ORDERED_CHOICE = No
    KEYATTR = Kiinteistötunnus Rakennuksen numero
    UNIQUE -> FeatureMerger_4 [REQUESTOR]
    DUPLICATE -> AttributeCreator
AttributeCreator
    ATTR_TABLE = SET_TO osarakennus = 1
    -> FeatureMerger_4 [REQUESTOR]
kiinteistotunnus_muunto
    KIINTEISTOTUNNUS = @Value(Kiinteistötunnus)
    KTMUOTO = 90500000000000
    Out -> AttributeManager_3
AttributeManager_3
    ATTR_TABLE:
      RENAME_SET_VALUE Tietuetunnus > TIETUE
      SET_TO KITU = @Substring(@Value(Kiinteistötunnus),0,17)
      SET_TO MALA = @TrimLeft(@Substring(@Value(Kiinteistötunnus),19,4),0)
      REMOVE Kiinteistötunnus
      RENAME_SET_VALUE Rakennuksen numero > RAKNRO
      RENAME_SET_VALUE Rakennuksen osan numero > RAKOSA
      RENAME_SET_VALUE Rakennustyyppi > RAKOSATYYP
      RENAME_SET_VALUE Rakentamisen alkupäivä > ALKUPVM
      RENAME_SET_VALUE Valmistumispäivä > VALMISPVM
      RENAME_SET_VALUE Rakennuksen osan kokonaispinta-ala (m2) > RAKOSAPA
      RENAME_SET_VALUE Rakennuksen osan tilavuus (m3) > RAKOSATIL
      RENAME_SET_VALUE Kantava rakenne > KANTARAK
      RENAME_SET_VALUE Peruskorjausvuosi > PERUSPARVU
      RENAME_SET_VALUE Ikäalennusten laskentavuosi > IKAVUOSI
      RENAME_SET_VALUE Viimeistelemättömän kellarin pinta-ala (m2) > VKELLARIPA
      RENAME_SET_VALUE Sähkö > SAHKOK
      RENAME_SET_VALUE Lämmitys > LAMMITYSK
      RENAME_SET_VALUE Vesijohto > VESIK
      RENAME_SET_VALUE Viemäri > VIEMARIK
      RENAME_SET_VALUE Talviasuttava > TALVIASK
      RENAME_SET_VALUE Kuistin pinta-ala (m2) > KUISTIPA
      RENAME_SET_VALUE WC > WCK
      RENAME_SET_VALUE Sauna > SAUNAK
      RENAME_SET_VALUE Rakennuksen muoto > MUOTO
      RENAME_SET_VALUE Varastotilojen pinta-ala (m2) > VARASTOPA
      RENAME_SET_VALUE Hissi > HISSIK
      RENAME_SET_VALUE Hissikuilujen pinta-ala (m2) > HISSIPA
      RENAME_SET_VALUE Ilmastointi > ISK
      RENAME_SET_VALUE Lämmitys ja vesi > LVK
      RENAME_SET_VALUE Kellaritilojen pinta-ala (m2) > KELLARIPA
      RENAME_SET_VALUE Paikoitusalueen pinta-ala (m2) > PALUEPA
      RENAME_SET_VALUE Pysäköintitalon ylin kerros katettu > PTALOKATE
      RENAME_SET_VALUE Lämpöeristys > ERISTEK
      RENAME_SET_VALUE Pysyvä rakennusnumero > RAKNRO_PYS
      RENAME_SET_VALUE VRK-rakennustyyppi > VRKRAKTYYP
      RENAME_SET_VALUE Käyttötarkoitus > KAYTTOTARK
      RENAME_SET_VALUE Purkukuntoinen > PURKUKUNTO
      RENAME_SET_VALUE Käyttökelvoton > KAYTTOKELV
      RENAME_SET_VALUE Ei kiinteistöveroa > EIKV
      RENAME_SET_VALUE Yleishyödyllisessä käytössä > YLEISHKAYT
      RENAME_SET_VALUE Rakennuksen verotusarvo  > VEROTUSARV = FME_CONDITIONAL:DEFAULT_VALUE'_FME_NO_OP_'BOOL_OP;OR;COMPOSITE_TEST;1;TEST @Value(osarakennus) = 1'0'FME_NUM_CONDITIONS2___
      RENAME_SET_VALUE Rakennuksen kiinteistövero  > KVRAKENNUS = FME_CONDITIONAL:DEFAULT_VALUE'_FME_NO_OP_'BOOL_OP;OR;COMPOSITE_TEST;1;TEST @Value(osarakennus) = 1'0'FME_NUM_CONDITIONS2___
      REMOVE col12
      REMOVE col13
      REMOVE col14
      REMOVE col15
      REMOVE col16
      REMOVE col17
      REMOVE col18
      REMOVE col19
      REMOVE col20
      REMOVE col21
      REMOVE col22
      REMOVE col23
      REMOVE col24
      REMOVE col25
      REMOVE col26
      REMOVE col27
      REMOVE col28
      REMOVE col33
      REMOVE col34
      REMOVE Maapohjan numero
      REMOVE Rakennusnumero
      RENAME_SET_VALUE Asiakastunnus > ASTUNNUS
      RENAME_SET_VALUE Asiakkaan nimi > ASNIMI
      RENAME_SET_VALUE Omistusosuus > OMOSUUS
      RENAME_SET_VALUE Hallintaosuus > HALOSUUS
      REMOVE Muun profiilin numero
      REMOVE Omistusosuus (osoittaja)
      REMOVE Omistusosuus (nimittäjä)
      REMOVE Hallintaosuus (osoittaja)
      REMOVE Hallintaosuus (nimittäjä)
      REMOVE Muu hallinta oikeus
      REMOVE osarakennus
      RENAME_SET_VALUE kiinteistotunnus > KIITUN
      REMOVE ktmuoto
      RENAME_SET_VALUE Siilotyyppi > SIILOTYYP
      RENAME_SET_VALUE Siilon halkaisija (m) > SIILOHALK
      RENAME_SET_VALUE Kasvihuoneen rakenne ja lämmitys > KHUONERAK
      RENAME_SET_VALUE Kevytrakenteinen ruokala > KRUOKALA
      REMOVE col29
      REMOVE col30
      REMOVE col31
      REMOVE col32
    -> AttributeCopier

Bookmark: Rakosat > Rakennus
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Kiinteistötunnus) @Value(Kiinteistötunnus) AUTO @Value(Rakennuksen numero) @Value(Rakennuksen numero) AUTO
    MERGE_TYPE = Attributes Only
    PROCESS_DUPS = YES
    REJECT_NULL_MISSING_KEYS = No
    SUPPLIERS_FIRST = No
    MERGED -> kiinteistotunnus_muunto [Kiinteistötunnus]

Bookmark: RAKTUN ja VTJPRT muodostus
AttributeCopier
    ATTR_TABLE = COPY RAKNRO > RAKNRO0
    -> StringPadder
StringPadder
    BLANK_ATTRIBUTE = Yes
    PADCHAR = 0
    SIDE = Left
    SRC_ATTRS = RAKNRO0
    WIDTH = 3
    -> StringConcatenator
StringConcatenator
    ACTION = Create New Attribute
    PARM_LINE = fme_basicstring:14%15:@Value(KIITUN)@Value(RAKNRO0)
    VAL_ATTR = RAKTUN
    -> StringLengthCalculator

Bookmark: Pituus astunnus-kentille
StringLengthCalculator
    LENGTH_ATTR = _astunnus_lista_pituus
    SRC_ATTR = ASTUNNUS
    -> StringLengthCalculator_2
StringLengthCalculator_2
    LENGTH_ATTR = _asnimi_lista_pituus
    SRC_ATTR = ASNIMI
    -> FeatureMerger_9 [REQUESTOR]

Bookmark: KTJ-Palstan sijaintitiedot
Note: Lisää OGC-API kyselyihin authkey
KiinteistorajanSijaintitiedot (reader OGCAPI_FEATURES_2)
    attributes: id int64, kiinteistorajalaji int64, lahdeaineisto int64, interpolointitapa int64
    -> AttributeExposer

Bookmark: Tilannekuva: KTJ-PALSTAN SIJAINTITIEDOT
KTJ_PALSTAN_SIJAINTITIEDOT: Inspector

Bookmark: KUNTA-VTJ VERTAILU
Note: VTJ-rakennusten linkitys VTJ-PRT:llä rakennusrekisterin rakennuksiin
FeatureMerger_18
    ATTR_ACCUM_MODE = Merge Supplier
    ATTR_CONFLICT_RES = Use Requestor
    IGNORE_NULLS = No
    JOIN_KEYS = @Value(PERMANENTB) @Value(Rakennustunnus) AUTO
    MERGE_TYPE = Attributes Only
    PROCESS_DUPS = NO
    REJECT_NULL_MISSING_KEYS = No
    SUPPLIERS_FIRST = No
    MERGED -> KUNTA-VTJ_-_VTJ-PRT_OK
    MERGED -> KUNTA-VTJ_-_VTJ-PRT_LINKITETTY (writer SHAPEFILE_4)
    MERGED -> Junction
    MERGED -> SpatialFilter_8 [Candidate]
    UNMERGED_REQUESTOR -> TestFilter_28
    UNMERGED_REQUESTOR -> SpatialFilter_9 [Candidate]
    UNMERGED_REQUESTOR -> KUNTA-VTJ_-_KUNNAN_RAKENNUSREK_VTJ-PRT_EI_LINKITETTY (writer SHAPEFILE_4)
    UNMERGED_REQUESTOR -> FeatureMerger [REQUESTOR]
    UNUSED_SUPPLIER -> TestFilter_23
    UNUSED_SUPPLIER -> KUNTA-VTJ_-_VTJ-RAK_VTJ-PRT_EI_LINKITETTY (writer SHAPEFILE_4)
TestFilter_28
    DEFAULT_VALUE = <UNFILTERED>
    TEST_LIST:
      "BOOL_OP,OR,COMPOSITE_TEST,""""""1 OR 2"""""",TEST_CLAUSE,TEST BUILDINGNU ATTRIBUTE_IS_MISSING ""
      TEST UNITLABEL ATTRIBUTE_IS_MISSING """,missing
    <UNFILTERED> -> FeatureMerger_19 [REQUESTOR]
KUNTA-VTJ_-_VTJ-PRT_OK: Inspector
TestFilter_23
    DEFAULT_VALUE = <UNFILTERED>
    TEST_LIST:
      "BOOL_OP,OR,COMPOSITE_TEST,""""""1 OR 2"""""",TEST_CLAUSE,TEST Raken-nus-numero ATTRIBUTE_IS_MISSING ""
      TEST Sijaintikiinteistön tunnus ATTRIBUTE_IS_MISSING """,missing
    <UNFILTERED> -> FeatureMerger_19 [SUPPLIER]
    <UNFILTERED> -> Bufferer
Note: VTJ-rakennusten linkitys muuttuvalla rakennustunnuksella rakennusrekisterin rakennuksiin
FeatureMerger_19
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(UNITLABEL) @Value(Sijaintikiinteistön tunnus) AUTO @Value(BUILDINGNU) @Value(Raken-nus-numero) AUTO
    MERGE_TYPE = Attributes Only
    PROCESS_DUPS = YES
    REJECT_NULL_MISSING_KEYS = No
    SUPPLIERS_FIRST = No
    MERGED -> KUNTA-VTJ_-_KTUNNUS_RAKNRO_OK
    MERGED -> Junction
    MERGED -> KUNTA-VTJ_-_MUUTTUVA_RAKENNUSTUNNUS_LINKITETTY (writer SHAPEFILE_4)
    UNMERGED_REQUESTOR -> KUNTA-VTJ_-_KUNNAN_RAKENNUSREK_VTJ-PRT_EI_LINKITETTY (writer SHAPEFILE_4) [off]
    UNUSED_SUPPLIER -> TestFilter_24
    UNUSED_SUPPLIER -> KUNTA-VTJ_-_MUUTTUVA_RAKENNUSNUMERO_EI_LINKITY_2
KUNTA-VTJ_-_KTUNNUS_RAKNRO_OK: Inspector

Bookmark: Tilannekuva: KUNTA-VTJ -VERTAILU - Kunnan rakennuksista puuttuu VTJ-PRT mutta linkittyy samaan pisteeseen
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> PointOnAreaOverlayer_Point
    PASSED -> FeatureMerger_2 [REQUESTOR]
    PASSED -> KUNTA-VTJ_-_SIJAINNILLA_LINKITETTY (writer SHAPEFILE_4)
    FAILED -> KUNTA-VTJ_-_MUUTTUVA_RAKENNUSNUMERO_EIKA_SIJAINTI_LINKITY
PointOnAreaOverlayer_Point: Inspector
KUNTA-VTJ_-_SIJAINNILLA_LINKITETTY (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), _predicate char(254)
Bufferer_Buffered: Inspector

Bookmark: Tilannekuva: KUNTA-VTJ -VERTAILU - Ei yhtenevät rakennukset rakennusrekisterin kanssa
KUNTA-VTJ_-_MUUTTUVA_RAKENNUSNUMERO_EIKA_SIJAINTI_LINKITY: Inspector

Bookmark: Tilannekuva:KUNTA-VTJ -VERTAILU - Sama piste eri VTJ-PRT
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_8_Passed
SpatialFilter_8_Passed: Inspector

Bookmark: Tilannekuva: KUNTA-VTJ: VTJ:stä poikkeavat rakennukset
KUNTA-VTJ_-_MUUTTUVA_RAKENNUSNUMERO_EI_LINKITY_2: Inspector

Bookmark: Esri shape: KUNTA-VTJ -VERTAILU - Yhtenevät rakennukset
KUNTA-VTJ_-_MUUTTUVA_RAKENNUSTUNNUS_LINKITETTY (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20)
KUNTA-VTJ_-_VTJ-PRT_LINKITETTY (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20)

Bookmark: Esri shape: KUNTA-VTJ -VERTAILU - Kunnan rakennusrekisterin ei yhtenevät rakennukset
KUNTA-VTJ_-_KUNNAN_RAKENNUSREK_VTJ-PRT_EI_LINKITETTY (writer SHAPEFILE_4)

Bookmark: Esri shape: KUNTA-VTJ -VERTAILU - VTJ-rakennusten ei yhtenevät rakennukset
KUNTA-VTJ_-_VTJ-RAK_VTJ-PRT_EI_LINKITETTY (writer SHAPEFILE_4)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20)

Bookmark: VEROTTAJAN RAKENNUKSIEN GEOKOODAUS
TestFilter_16
    DEFAULT_VALUE = <UNFILTERED>
    TEST_LIST = "BOOL_OP,OR,COMPOSITE_TEST,""""""1"""""",TEST_CLAUSE,TEST @Value(BUILDINGRE) = 1",@Value(BUILDINGREGSTATUS) = 1,"BOOL_OP,OR,COMPOSITE_TEST,""""""1"""""",TEST_CLAUSE,TEST @Value(BUILDINGRE) = 2",@Value(BUILDINGREGSTATUS) = 2
    @Value(BUILDINGREGSTATUS) = 1 -> TestFilter_17
    @Value(BUILDINGREGSTATUS) = 2 -> TestFilter_18
TestFilter_17
    DEFAULT_VALUE = <UNFILTERED>
    TEST_LIST = "BOOL_OP,OR,COMPOSITE_TEST,""""""1"""""",TEST_CLAUSE,TEST @Value(PERMANENTB) = """,PERMANENTBUILDINGLABE
    <UNFILTERED> -> FeatureMerger_10 [SUPPLIER]
    <UNFILTERED> -> AttributeCreator_4
AttributeCreator_4
    ATTR_LIST = Rak_nro,@Value(BUILDINGNU)
    -> AttributeTrimmer_4
AttributeTrimmer_4
    SRC_ATTRS = Rak_nro
    TRIM_CHARS = 0
    TRIM_TO_NONE = No
    TRIM_TYPE = Left
    -> FeatureMerger_11 [SUPPLIER]
TestFilter_18
    DEFAULT_VALUE = <UNFILTERED>
    TEST_LIST = "BOOL_OP,OR,COMPOSITE_TEST,""""""1"""""",TEST_CLAUSE,TEST @Value(PERMANENTB) = """,PERMANENTBUILDINGLABEL
    <UNFILTERED> -> AttributeCreator_5
    <UNFILTERED> -> FeatureMerger_12 [SUPPLIER]
AttributeCreator_5
    ATTR_LIST = Rak_nro,@Value(BUILDINGNU)
    -> AttributeTrimmer_5
AttributeTrimmer_5
    SRC_ATTRS = Rak_nro
    TRIM_CHARS = 0
    TRIM_TO_NONE = No
    TRIM_TYPE = Left
    -> FeatureMerger_13 [SUPPLIER]
Note: Kunnan VRK-rakennustiedot, jotka ajettu Esri shape muotoon
TestFilter_8
    DEFAULT_VALUE = <UNFILTERED>
    TEST_LIST = "BOOL_OP,OR,COMPOSITE_TEST,""""""1"""""",TEST_CLAUSE,TEST @Value(Voimassaol) = 1",voimassa
    voimassa -> FeatureMerger_9 [SUPPLIER]
    voimassa -> FeatureMerger_8 [SUPPLIER]
Note: VERO/VRK VTJ-PRT
FeatureMerger_9
    JOIN_KEYS = @Value(RAKNRO_PYS) @Value(RakTunnus) AUTO
    MERGE_TYPE = Geometry
    PROCESS_DUPS = No
    SUPPLIERS_FIRST = No
    MERGED -> AttributeKeeper_4
    NOT_MERGED -> FeatureMerger_8 [REQUESTOR]
Note: VERO/VRK KTUNNUS+RAKNRO
FeatureMerger_8
    ATTR_ACCUM_MODE = Merge Supplier
    ATTR_CONFLICT_RES = Use Requestor
    IGNORE_NULLS = No
    JOIN_KEYS = @Value(KIITUN) @Value(KiintTunnu) AUTO @Value(RAKNRO0) @Value(RakNumero) AUTO
    MERGE_TYPE = Attributes and Geometry
    PROCESS_DUPS = No
    SUPPLIERS_FIRST = No
    MERGED -> AttributeKeeper_4
    NOT_MERGED -> FeatureMerger_10 [REQUESTOR]
Note: Loput kunnan rak.rekisteristä vtj-prt:llä
FeatureMerger_10
    JOIN_KEYS = @Value(RAKNRO_PYS) @Value(PERMANENTB) AUTO
    MERGE_TYPE = Geometry
    PROCESS_DUPS = No
    SUPPLIERS_FIRST = No
    MERGED -> AttributeKeeper_4
    NOT_MERGED -> FeatureMerger_11 [REQUESTOR]
FeatureMerger_11
    JOIN_KEYS = @Value(KIITUN) @Value(UNITLABEL) AUTO @Value(RAKNRO0) @Value(Rak_nro) AUTO
    MERGE_TYPE = Geometry
    PROCESS_DUPS = No
    SUPPLIERS_FIRST = No
    MERGED -> AttributeKeeper_4
    NOT_MERGED -> FeatureMerger_12 [REQUESTOR]
FeatureMerger_12
    JOIN_KEYS = @Value(RAKNRO_PYS) @Value(PERMANENTB) AUTO
    MERGE_TYPE = Geometry
    PROCESS_DUPS = No
    SUPPLIERS_FIRST = No
    MERGED -> AttributeKeeper_4
    MERGED -> FeatureMerger_12_Merged
    NOT_MERGED -> FeatureMerger_13 [REQUESTOR]
FeatureMerger_12_Merged: Inspector
FeatureMerger_13
    JOIN_KEYS = @Value(KIITUN) @Value(UNITLABEL) AUTO @Value(RAKNRO0) @Value(Rak_nro) AUTO
    MERGE_TYPE = Geometry
    PROCESS_DUPS = No
    SUPPLIERS_FIRST = No
    MERGED -> AttributeKeeper_4
    NOT_MERGED -> FeatureMerger_6_NotMerged
    NOT_MERGED -> VertexCreator_5
FeatureMerger_6_NotMerged: Inspector [off]
VertexCreator_5
    MODE_NAME = Replace with Point
    XVAL = 22480000
    YVAL = 7000000
    -> CoordinateSystemSetter
CoordinateSystemSetter
    COORDSYS = EPSG:3876
    -> Reprojector_5
Reprojector_5
    DEST = EPSG:3067
    INTERPOLATION_TYPE_NAME = Nearest Neighbor
    RASTER_CELL_SIZE = Preserve Cells
    RASTER_TOLERANCE = 0.0
    SOURCE = EPSG:3876
    REPROJECTED -> AttributeKeeper_4
AttributeKeeper_4
    CREATE_BULK_MODE_FEATURES = NO
    KEEP_ATTRS = TALVIASK,KIITUN,WCK,KUISTIPA,KELLARIPA,ERISTEK,VIEMARIK,KVRAKENNUS,SAHKOK,HISSIPA,IKAVUOSI,ISK,LVK,KITU,VESIK,RAKTUN,VARASTOPA,VKELLARIPA,MALA,HISSIK,RAKNRO,SAUNAK,LAMMITYSK,RAKOSA,ALKUPVM,ASNIMI,ASTUNNUS,EIKV,HALOSUUS,KANTARAK,KAYTTOKELV,KAYTTOTARK,MUOTO,OMOSUUS,PALUEPA,PERUSPARVU,PTALOKATE,PURKUKUNTO,RAKNRO_PYS,RAKOSAPA,RAKOSATIL,RAKOSATYYP,VALMISPVM,VEROTUSARV,VRKRAKTYYP,YLEISHKAYT,KHUONERAK,KRUOKALA,SIILOHALK,SIILOTYYP
    -> AttributeManager_4
AttributeManager_4
    -> VEROANALYYSI (writer SHAPE_1)
    -> vertailu
    -> TestFilter_7
    -> FeatureMerger_28 [SUPPLIER]
vertailu: Inspector

Bookmark: VTJ-PRT -ANALYYSIN LINKITYS
Note: VTJ-PRT-analyysin linkitys KUNTA-VTJ-VERTAILUN ei linkittyviin kuntarekisterin rakennuksiin
FeatureMerger
    ATTR_ACCUM_MODE = Merge Supplier
    ATTR_CONFLICT_RES = Use Requestor
    IGNORE_NULLS = No
    JOIN_KEYS = @Value(PERMANENTB) @Value(VTJPRT) AUTO
    MERGE_TYPE = Attributes Only
    PROCESS_DUPS = NO
    REJECT_NULL_MISSING_KEYS = Yes
    SUPPLIERS_FIRST = No
    MERGED -> TestFilter_4
    MERGED -> Junction
TestFilter_4
    DEFAULT_VALUE = <UNFILTERED>
    TEST_LIST = "BOOL_OP,OR,COMPOSITE_TEST,""""""1"""""",TEST_CLAUSE,CASE_INSENSITIVE_TEST @Value(Tn) CONTAINS @Value(T6)",!=T6
    !=T6 -> VTJ-PRT-ANALYYSI_T1-T4_SIJAINNILLA_LINKITETYT_2
    !=T6 -> VTJ-PRT-ANALYYSI_T1-T4_T6_KUNTAREK_VTJPRT_LINKITYS (writer SHAPEFILE_5)
    <UNFILTERED> -> VTJ-PRT-ANALYYSI_T1-T4_SIJAINNILLA_LINKITETYT_2
    <UNFILTERED> -> VTJ-PRT-ANALYYSI_T1-T4_T6_KUNTAREK_VTJPRT_LINKITYS (writer SHAPEFILE_5)
VTJ-PRT-ANALYYSI_T1-T4_SIJAINNILLA_LINKITETYT_2: Inspector
Note: VTJ-PRT-analyysin linkitys KUNTA-VTJ-VERTAILUN sijainnilla linkittyvien rakennuksien kanssa
FeatureMerger_2
    ATTR_ACCUM_MODE = Merge Supplier
    ATTR_CONFLICT_RES = Use Requestor
    IGNORE_NULLS = No
    JOIN_KEYS = @Value(PERMANENTB) @Value(VTJPRT) AUTO
    MERGE_TYPE = Attributes and Geometry
    PROCESS_DUPS = NO
    REJECT_NULL_MISSING_KEYS = No
    SUPPLIERS_FIRST = No
    MERGED -> TestFilter_14
TestFilter_14
    DEFAULT_VALUE = <UNFILTERED>
    TEST_LIST = "BOOL_OP,OR,COMPOSITE_TEST,""""""1"""""",TEST_CLAUSE,CASE_INSENSITIVE_TEST @Value(Tn) CONTAINS @Value(T6)",!=T6
    !=T6 -> VTJ-PRT-ANALYYSI_T1-T4_SIJAINNILLA_LINKITETYT
    !=T6 -> VTJ-PRT-ANALYYSI_T1-T4_SIJAINNILLA_LINKITETYT (writer SHAPEFILE_5)
VTJ-PRT-ANALYYSI_T1-T4_SIJAINNILLA_LINKITETYT: Inspector
VTJ-PRT-ANALYYSI_T1-T4_SIJAINNILLA_LINKITETYT (writer SHAPEFILE_5)
    attributes: Alkupäivä date, Loppupäivä date, Kaava number(2,0), Tilavuus number(6,0), Sähkö number(2,0), Kaasu number(2,0), Viemäri number(2,0), Vesijohto number(2,0), Hissi number(2,0), Tn char(3), Id number(11,0), XI number(10,3), YP number(11,3), Kä char(48), Pa number(5,0), Ke char(11), VTJPRT char(11), VTJXI number(10,3), VTJXP number(11,3), VTJKä char(69), VTJPa number(5,0), VTJKe number(2,0), T1 number(2,0), T2 char(254), T3 char(254), T4 char(254), T5 char(254), T6 char(254), Käv char(1), Pav char(254),
      Kev char(254)
Note: VTJ-PRT-analyysin linkitys KUNTA-VTJ-VERTAILUN ei linkittyviin VTJ-rakennuksiin
FeatureMerger_23
    ATTR_ACCUM_MODE = Merge Supplier
    ATTR_CONFLICT_RES = Use Requestor
    IGNORE_NULLS = No
    JOIN_KEYS = @Value(Rakennustunnus) @Value(VTJPRT) AUTO
    MERGE_TYPE = Attributes and Geometry
    PROCESS_DUPS = NO
    REJECT_NULL_MISSING_KEYS = No
    SUPPLIERS_FIRST = No
    MERGED -> TestFilter_27
Note: T1-T4 rakennuksilla mahdollinen korjattu sijaintipiste rakennuksen painopisteeseen
TestFilter_27
    DEFAULT_VALUE = <UNFILTERED>
    TEST_LIST = "BOOL_OP,OR,COMPOSITE_TEST,""""""1"""""",TEST_CLAUSE,CASE_INSENSITIVE_TEST @Value(Tn) CONTAINS @Value(T6)",!=T6
    !=T6 -> VTJ-PRT-ANALYYSI
    !=T6 -> VTJ-PRT-UUDET_RAKENNUKSET_T1-4 (writer SHAPEFILE_5)
    !=T6 -> FeatureMerger_28 [REQUESTOR]
    !=T6 -> FeatureMerger_21 [REQUESTOR]
    <UNFILTERED> -> FeatureMerger_28 [REQUESTOR]
    <UNFILTERED> -> VTJ-PRT-UUDET_RAKENNUKSET_T6 (writer SHAPEFILE_5)
    <UNFILTERED> -> VTJ-PRT-ANALYYSI
    <UNFILTERED> -> FeatureMerger_21 [REQUESTOR]

Bookmark: VEROTETTAVIEN RAKENNUSTEN VERTAILU
Note: Rejected portissa on Verottajan rakennuksenosia
Junction
    -> FeatureMerger_28 [REQUESTOR]
    -> FeatureMerger_24 [REQUESTOR]
Note: Filteröidään rakennuksen osat pois
TestFilter_7
    DEFAULT_VALUE = <UNFILTERED>
    TEST_LIST = "BOOL_OP,OR,COMPOSITE_TEST,""""""1"""""",TEST_CLAUSE,TEST @Value(RAKOSA) = 1",RAKOSA=1
    RAKOSA=1 -> FeatureMerger_21 [SUPPLIER]
Bufferer_5
    ANGLE = 22.5
    CAP_STYLE = Arc
    CORNER_STYLE = Arc
    MODE = AREA
    OFFSET = 1
    OFFSET_UNITS = NONE
    PRECISION = APPROX
    BUFFERED -> SpatialFilter_7 [Filter]
Reprojector_6
    DEST = EPSG:3067
    INTERPOLATION_TYPE_NAME = Nearest Neighbor
    RASTER_CELL_SIZE = Preserve Cells
    RASTER_TOLERANCE = 0.0
    SOURCE = ETRS89.FinGK-25/10_FME
    REPROJECTED -> CoordinateSystemSetter_3
CoordinateSystemSetter_3
    COORDSYS = EPSG:3067
    -> SpatialFilter_4 [Candidate]
Bufferer_3
    ANGLE = 22.5
    CAP_STYLE = Arc
    CORNER_STYLE = Arc
    MODE = AREA
    OFFSET = 1
    OFFSET_UNITS = NONE
    PRECISION = APPROX
    BUFFERED -> SpatialFilter_4 [Filter]
Note: NÄITÄ SIJAINTILINKITYKSIÄ EI PITÄISI TARVITA. Nämä ei linkittynyt muuttuvalla rakennustunnuksella mutta sijainnilla linkiityi Verottajan rakennuksiin. Olivat saaneet eri kiinteistötunnus attribuutilla sijiannin P3 vaiheessa mitä tässä P4 vaiheessa käytettiin muuttuvan rakennustunnuksen linkityksessä.
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> KUNNANREK_VEROANALYYSI_VTJ-PRT_LINKITTYVÄT (writer SHAPEFILE_7)
    PASSED -> KUNNANREK_VEROANALYYSI_VTJ-PRT_LINKITTYVÄT
    PASSED -> Bufferer_4
    FAILED -> SpatialFilter_7 [Candidate]
Note: NÄITÄ SIJAINTILINKITYKSIÄ EI PITÄISI TARVITA. Nämä ei linkittynyt muuttuvalla rakennustunnuksella mutta sijainnilla linkiityi Verottajan rakennuksiin. Olivat saaneet eri kiinteistötunnus attribuutilla sijiannin P3 vaiheessa mitä tässä P4 vaiheessa käytettiin muuttuvan rakennustunnuksen linkityksessä.
SpatialFilter_7
    AGGREGATE_HANDLING = Yes
    BASE_TYPE = Multiple Filters
    CURVE_BOUNDARY_RULE_PARAM = Default Rule
    PASS_CRITERIA = Pass Against One Filter
    PREDATTR = _predicate
    PREDICATES = CONTAINS
    USE_BOUNDING_BOX = No
    PASSED -> Bufferer_6
    FAILED -> VEROANALYYSI_EI_LINKITY (writer SHAPEFILE_8)
Bufferer_6
    ANGLE = 22.5
    CAP_STYLE = Arc
    CORNER_STYLE = Arc
    MODE = AREA
    OFFSET = 1
    OFFSET_UNITS = NONE
    PRECISION = APPROX
    BUFFERED -> SpatialFilter_10 [Filter]
SpatialFilter_10
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> VEROANALYYSI_VTJ-PRT-ANALYYSI_LINKITTYVAT (writer SHAPEFILE_6)
    FAILED -> VEROANALYYSI_VTJ-PRT-ANALYYSI_UUDET_VEROANALYYSILLE (writer SHAPEFILE_6)
Note: Näiden joukossa virheellisiä jotka käytävä läpi. Tarkoittaa että pitää korjata VTJ-rakennuksia VTJ:ssä.
VEROANALYYSI_VTJ-PRT-ANALYYSI_LINKITTYVAT (writer SHAPEFILE_6)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254), KITU char(200), RAKNRO char(200), KIITUN char(200), RAKTUN char(254), MALA char(200), RAKOSA char(200), RAKOSATYYP char(200), ALKUPVM char(200), VALMISPVM char(200), RAKOSAPA char(200), RAKOSATIL char(200), KANTARAK char(200), PERUSPARVU char(200), IKAVUOSI char(200), VKELLARIPA char(200), SAHKOK char(200), LAMMITYSK char(200), VESIK char(200),
      VIEMARIK char(200), TALVIASK char(200), KUISTIPA char(200), WCK char(200), SAUNAK char(200), MUOTO char(200), VARASTOPA char(200), HISSIK char(200), HISSIPA char(200), ISK char(200), LVK char(200), KELLARIPA char(200), PALUEPA char(200), PTALOKATE char(200), ERISTEK char(200), RAKNRO_PYS char(200), VRKRAKTYYP char(200), KAYTTOTARK char(200), PURKUKUNTO char(200), KAYTTOKELV char(200), EIKV char(200), YLEISHKAYT char(200), VEROTUSARV char(200), KVRAKENNUS char(200), ASTUNNUS char(200), ASNIMI char(200), OMOSUUS char(200), HALOSUUS char(200), SIILOTYYP char(200), SIILOHALK char(200),
      KHUONERAK char(200), KRUOKALA char(200), fme_reject char(254)
Note: Näiden joukossa virheellisiä jotka käytävä läpi. Tarkoittaa että pitää korjata VTJ-rakennuksia VTJ:ssä.
Note: OSA NÄISTÄ UUSIA, OSA EI VEROTETTAVIA
VEROANALYYSI_VTJ-PRT-ANALYYSI_UUDET_VEROANALYYSILLE (writer SHAPEFILE_6)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254)
Bufferer_4
    ANGLE = 22.5
    CAP_STYLE = Arc
    CORNER_STYLE = Arc
    MODE = AREA
    OFFSET = 1
    OFFSET_UNITS = NONE
    PRECISION = APPROX
    BUFFERED -> SpatialFilter_5 [Filter]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> KUNNANREK_VEROANALYYSI_EI_LINKITY (writer SHAPEFILE_8)
    FAILED -> KUNNANREK_VEROANALYYSI_EI_LINKITY
KTUNNUS_KUNTAVERO_UNUSEDSUPPLIER (writer SHAPEFILE_8)
    attributes: KITU char(200), RAKNRO char(200), KIITUN char(200), RAKTUN char(254), MALA char(200), RAKOSA char(200), RAKOSATYYP char(200), ALKUPVM char(200), VALMISPVM char(200), RAKOSAPA char(200), RAKOSATIL char(200), KANTARAK char(200), PERUSPARVU char(200), IKAVUOSI char(200), VKELLARIPA char(200), SAHKOK char(200), LAMMITYSK char(200), VESIK char(200), VIEMARIK char(200), TALVIASK char(200), KUISTIPA char(200), WCK char(200), SAUNAK char(200), MUOTO char(200), VARASTOPA char(200), HISSIK char(200), HISSIPA char(200), ISK char(200), LVK char(200), KELLARIPA char(200),
      PALUEPA char(200), PTALOKATE char(200), ERISTEK char(200), RAKNRO_PYS char(254), VRKRAKTYYP char(254), KAYTTOTARK char(254), PURKUKUNTO char(254), KAYTTOKELV float, EIKV char(254), YLEISHKAYT char(254), VEROTUSARV char(254), KVRAKENNUS double, ASTUNNUS char(254), ASNIMI char(254), OMOSUUS char(200), HALOSUUS char(200), SIILOTYYP char(200), SIILOHALK char(200), KHUONERAK char(200), KRUOKALA char(200)

Bookmark: Esri shape: VTJ-PRT-analyysi T1-4 uudet rakennukset
VTJ-PRT-UUDET_RAKENNUKSET_T1-4 (writer SHAPEFILE_5)
    attributes: Alkupäivä date, Loppupäivä date, Kaava number(2,0), Tilavuus number(6,0), Sähkö number(2,0), Kaasu number(2,0), Viemäri number(2,0), Vesijohto number(2,0), Hissi number(2,0), Tn char(3), Id number(11,0), XI number(10,3), YP number(11,3), Kä char(48), Pa number(5,0), Ke char(11), VTJPRT char(11), VTJXI number(10,3), VTJXP number(11,3), VTJKä char(69), VTJPa number(5,0), VTJKe number(2,0), T1 number(2,0), T2 char(254), T3 char(254), T4 char(254), T5 char(254), T6 char(254), Käv char(1), Pav char(254),
      Kev char(254)

Bookmark: Esri shape: VTJ-PRT-analyysi T6 uudet rakennukset
VTJ-PRT-UUDET_RAKENNUKSET_T6 (writer SHAPEFILE_5)
    attributes: Alkupäivä date, Loppupäivä date, Kaava number(2,0), Tilavuus number(6,0), Sähkö number(2,0), Kaasu number(2,0), Viemäri number(2,0), Vesijohto number(2,0), Hissi number(2,0), Tn char(3), Id number(11,0), XI number(10,3), YP number(11,3), Kä char(48), Pa number(5,0), Ke char(11), VTJPRT char(11), VTJXI number(10,3), VTJXP number(11,3), VTJKä char(69), VTJPa number(5,0), VTJKe number(2,0), T1 number(2,0), T2 char(254), T3 char(254), T4 char(254), T5 char(254), T6 char(254), Käv char(1), Pav char(254),
      Kev char(254)

Bookmark: Tilannekuva: VTJ-PRT-analyysi T1-4 ja T6 uudet rakennukset
VTJ-PRT-ANALYYSI: Inspector

Bookmark: MML PRT_linkitys_geopackages
Referenssipisteet_T1_T2_T3_T4 (reader OGCGEOPACKAGE_1)
    attributes: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
viivat_T1_T2_T3_T4 (reader OGCGEOPACKAGE_1)
    attributes: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
T1 (reader OGCGEOPACKAGE_1)
    attributes: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
T2 (reader OGCGEOPACKAGE_1)
    attributes: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
T3 (reader OGCGEOPACKAGE_1)
    attributes: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
T4 (reader OGCGEOPACKAGE_1)
    attributes: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
T5 (reader OGCGEOPACKAGE_1)
    attributes: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
T6 (reader OGCGEOPACKAGE_1)
    attributes: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

Bookmark: VRK-rakennukset lähtödata
VRK_rak_20210819 (reader SHAPEFILE_2)
    attributes: RakTunnus varchar(11), SijKunta short, Rak_Tila short, Muutoslaji varchar(3), Alkupaiva date, Loppupaiva date, Voimassaol short, Lisayspaiv date, SijKiint number(15,0), KiintNimi varchar(100), KiintTunnu number(15,0), Tarkistusm varchar(2), RakNumero short, KiintMANro varchar(254), Postinro long, ValmistPva date, RakLuvanVa date, PoikkLupa short, Tietolahde short, Perusparan short, PerusparPv date, Kaava short, HallintPer short, Julkisivum short, Kerrosala long, KerrAlanMu date, Kerrosluku short, KerrLuvunM date, Kokonaisal long, KokonAlanM date,
      Huoneistoa varchar(254), HuonAlanMu varchar(254), Tilavuus long, TilavMuuto date, Kellariala long, Kaytossaol short, KaytOlonMu date, Kayttotark short, KayttotaMu date, Lammitysta short, LammTavanM date, Polttoaine short, PolttoaiMu date, RakMateria short, Rungon_rak short, VarMuutosP date, Sahko short, Kaasu short, Viemari short, Vesijohto short, Lammin_ves short, Aurinkopan short, Hissi short, Ilmastoint short, Sauna_lkm short, Vaestosuoj short, Verkostoli date, Viemarilii short, Vesijohtol short, Sahkoliitt short,
      Kaasuliitt varchar(254), Kaapelilii short, Pohjoiskoo long, Itakoordin long, KoordVarmu varchar(2), Astyyppi short, aanAlKunta short, aanAlue long, Tuleva_kun short, Tuleva_aan long, KtarkLahde varchar(9), RakLuokka long, RakLMuutos date, RakLLahde varchar(20)
    -> TestFilter_8

Bookmark: T1-T4 ja T6 rakennusten linkitys
FeatureMerger_21
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(Rakennustunnus) @Value(RAKNRO_PYS) AUTO
    MERGE_TYPE = Attributes Only
    PROCESS_DUPS = YES
    REJECT_NULL_MISSING_KEYS = No
    SUPPLIERS_FIRST = No
    MERGED -> VEROANALYYSI_VTJ-PRT-ANALYYSI_LINKITTYVAT (writer SHAPEFILE_6)
    UNMERGED_REQUESTOR -> FeatureMerger_26 [SUPPLIER]
    UNUSED_SUPPLIER -> FeatureMerger_24 [SUPPLIER]

Bookmark: Muuttuvan rakennustunnuksen lisääminen VTJ-PRT-analyysin rakennuksille
FeatureMerger_26
    ATTR_ACCUM_MODE = Merge Supplier
    ATTR_CONFLICT_RES = Use Requestor
    IGNORE_NULLS = No
    JOIN_KEYS = @Value(Rakennustunnus) @Value(VTJPRT) AUTO
    MERGE_TYPE = Attributes and Geometry
    PROCESS_DUPS = NO
    REJECT_NULL_MISSING_KEYS = No
    SUPPLIERS_FIRST = No
    MERGED -> TestFilter_30
TestFilter_30
    DEFAULT_VALUE = <UNFILTERED>
    TEST_LIST:
      "BOOL_OP,OR,COMPOSITE_TEST,""""""1 OR 2"""""",TEST_CLAUSE,TEST Raken-nus-numero ATTRIBUTE_IS_MISSING ""
      TEST Sijaintikiinteistön tunnus ATTRIBUTE_IS_MISSING """,missing
    <UNFILTERED> -> FeatureMerger_27 [REQUESTOR]

Bookmark: VTJ-PRT-linkitys
FeatureMerger_24
    ATTR_ACCUM_MODE = Merge Supplier
    ATTR_CONFLICT_RES = Use Requestor
    IGNORE_NULLS = No
    JOIN_KEYS = @Value(PERMANENTB) @Value(RAKNRO_PYS) AUTO
    MERGE_TYPE = Attributes Only
    PROCESS_DUPS = NO
    REJECT_NULL_MISSING_KEYS = No
    SUPPLIERS_FIRST = No
    MERGED -> KUNNANREK_VEROANALYYSI_VTJ-PRT_LINKITTYVÄT
    MERGED -> KUNNANREK_VEROANALYYSI_VTJ-PRT_LINKITTYVÄT (writer SHAPEFILE_7)
    UNMERGED_REQUESTOR -> FeatureMerger_22 [REQUESTOR]
    UNUSED_SUPPLIER -> FeatureMerger_22 [SUPPLIER]
    <REJECTED> -> FeatureMerger_22 [SUPPLIER]

Bookmark: Muuttuvalla kiinteistötunnuksella linkitys
FeatureMerger_22
    ATTR_ACCUM_MODE = Merge Supplier
    ATTR_CONFLICT_RES = Use Requestor
    IGNORE_NULLS = No
    JOIN_KEYS = @Value(UNITLABEL) @Value(KIITUN) AUTO @Value(BUILDINGNU) @Value(RAKNRO) AUTO
    MERGE_TYPE = Attributes Only
    PROCESS_DUPS = NO
    REJECT_NULL_MISSING_KEYS = No
    SUPPLIERS_FIRST = No
    MERGED -> KUNNANREK_VEROANALYYSI_VTJ-PRT_LINKITTYVÄT (writer SHAPEFILE_7)
    MERGED -> KUNNANREK_VEROANALYYSI_VTJ-PRT_LINKITTYVÄT
    UNMERGED_REQUESTOR -> FeatureMerger_3 [REQUESTOR]
    UNUSED_SUPPLIER -> FeatureMerger_3 [SUPPLIER]
    <REJECTED> -> FeatureMerger_3 [SUPPLIER]
FeatureMerger_3
    ATTR_ACCUM_MODE = Merge Supplier
    ATTR_CONFLICT_RES = Use Requestor
    IGNORE_NULLS = No
    JOIN_KEYS = @Value(Sijaintikiinteistön tunnus) @Value(KIITUN) AUTO @Value(Raken-nus-numero) @Value(RAKNRO) AUTO
    MERGE_TYPE = Attributes Only
    PROCESS_DUPS = NO
    REJECT_NULL_MISSING_KEYS = No
    SUPPLIERS_FIRST = No
    MERGED -> KUNNANREK_VEROANALYYSI_VTJ-PRT_LINKITTYVÄT (writer SHAPEFILE_7)
    MERGED -> KUNNANREK_VEROANALYYSI_VTJ-PRT_LINKITTYVÄT
    UNMERGED_REQUESTOR -> SpatialFilter_5 [Candidate]
    UNMERGED_REQUESTOR -> Bufferer_3
    UNUSED_SUPPLIER -> FeatureMerger_27 [SUPPLIER]
    <REJECTED> -> FeatureMerger_27 [SUPPLIER]

Bookmark: VTJ-PRT-analyysin linkitys muuttuvalla rakennustunnuksella
FeatureMerger_27
    ATTR_ACCUM_MODE = Merge Supplier
    ATTR_CONFLICT_RES = Use Requestor
    IGNORE_NULLS = No
    JOIN_KEYS = @Value(Sijaintikiinteistön tunnus) @Value(KIITUN) AUTO @Value(Raken-nus-numero) @Value(RAKNRO) AUTO
    MERGE_TYPE = Attributes Only
    PROCESS_DUPS = NO
    REJECT_NULL_MISSING_KEYS = No
    SUPPLIERS_FIRST = No
    MERGED -> VEROANALYYSI_VTJ-PRT-ANALYYSI_MUUTTUVALLA_RAKENNUSTUNNUKSELLA_LINKITTYVÄT
    MERGED -> VEROANALYYSI_VTJ-PRT-ANALYYSI_LINKITTYVAT (writer SHAPEFILE_6)
    UNMERGED_REQUESTOR -> Bufferer_5
    UNMERGED_REQUESTOR -> SpatialFilter_10 [Candidate]
    UNUSED_SUPPLIER -> Reprojector_6
    <REJECTED> -> Reprojector_6

Bookmark: Verottajan aineisto joka ei linkity kuntarekisterin/VTJ-rakennusten kanssa
VEROANALYYSI_EI_LINKITY (writer SHAPEFILE_8)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254), KITU char(200), RAKNRO char(200), KIITUN char(200), RAKTUN char(254), MALA char(200), RAKOSA char(200), RAKOSATYYP char(200), ALKUPVM char(200), VALMISPVM char(200), RAKOSAPA char(200), RAKOSATIL char(200), KANTARAK char(200), PERUSPARVU char(200), IKAVUOSI char(200), VKELLARIPA char(200), SAHKOK char(200), LAMMITYSK char(200), VESIK char(200),
      VIEMARIK char(200), TALVIASK char(200), KUISTIPA char(200), WCK char(200), SAUNAK char(200), MUOTO char(200), VARASTOPA char(200), HISSIK char(200), HISSIPA char(200), ISK char(200), LVK char(200), KELLARIPA char(200), PALUEPA char(200), PTALOKATE char(200), ERISTEK char(200), RAKNRO_PYS char(200), VRKRAKTYYP char(200), KAYTTOTARK char(200), PURKUKUNTO char(200), KAYTTOKELV char(200), EIKV char(200), YLEISHKAYT char(200), VEROTUSARV char(200), KVRAKENNUS char(200), ASTUNNUS char(200), ASNIMI char(200), OMOSUUS char(200), HALOSUUS char(200), SIILOTYYP char(200), SIILOHALK char(200),
      KHUONERAK char(200), KRUOKALA char(200), fme_reject char(254)

Bookmark: Tilannekuva: KUNTAREK_VEROANALYYSI_LINKITTYVAT
KUNNANREK_VEROANALYYSI_VTJ-PRT_LINKITTYVÄT: Inspector

Bookmark: Esri shape: KUNTAREK_VEROANALYYSI_LINKITTYVAT
KUNNANREK_VEROANALYYSI_VTJ-PRT_LINKITTYVÄT (writer SHAPEFILE_7)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254), KITU char(200), RAKNRO char(200), KIITUN char(200), RAKTUN char(254), MALA char(200), RAKOSA char(200), RAKOSATYYP char(200), ALKUPVM char(200), VALMISPVM char(200), RAKOSAPA char(200), RAKOSATIL char(200), KANTARAK char(200), PERUSPARVU char(200), IKAVUOSI char(200), VKELLARIPA char(200), SAHKOK char(200), LAMMITYSK char(200), VESIK char(200),
      VIEMARIK char(200), TALVIASK char(200), KUISTIPA char(200), WCK char(200), SAUNAK char(200), MUOTO char(200), VARASTOPA char(200), HISSIK char(200), HISSIPA char(200), ISK char(200), LVK char(200), KELLARIPA char(200), PALUEPA char(200), PTALOKATE char(200), ERISTEK char(200), RAKNRO_PYS char(200), VRKRAKTYYP char(200), KAYTTOTARK char(200), PURKUKUNTO char(200), KAYTTOKELV char(200), EIKV char(200), YLEISHKAYT char(200), VEROTUSARV char(200), KVRAKENNUS char(200), ASTUNNUS char(200), ASNIMI char(200), OMOSUUS char(200), HALOSUUS char(200), SIILOTYYP char(200), SIILOHALK char(200),
      KHUONERAK char(200), KRUOKALA char(200), fme_reject char(254)

Bookmark: Esri shape: KUNTAREK_VEROANALYYSI_EI_LINKITY
KUNNANREK_VEROANALYYSI_EI_LINKITY (writer SHAPEFILE_8)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254)

Bookmark: Tilannekuva: KUNTAREK_VEROANALYYSI_EI_LINKITY
KUNNANREK_VEROANALYYSI_EI_LINKITY: Inspector

Bookmark: Kiinteistötunnuksella linkitys
FeatureMerger_28
    ATTR_ACCUM_MODE = Merge Supplier
    ATTR_CONFLICT_RES = Use Requestor
    IGNORE_NULLS = No
    JOIN_KEYS = @Value(UNITLABEL) @Value(KIITUN) AUTO
    MERGE_TYPE = Attributes Only
    PROCESS_DUPS = NO
    REJECT_NULL_MISSING_KEYS = No
    SUPPLIERS_FIRST = No
    UNMERGED_REQUESTOR -> KTUNNUS_KUNTAVERO_UNMERGE (writer SHAPEFILE_8)
    UNUSED_SUPPLIER -> KTUNNUS_KUNTAVERO_UNUSEDSUPPLIER (writer SHAPEFILE_8)

Bookmark: Esri shape - Kiinteistötunnuksella linkitetyt
KTUNNUS_KUNTAVERO_UNMERGE (writer SHAPEFILE_8)
    attributes: Rakennustu char(11), Sijainti_k number(4,0), Raken_nuks number(3,0), Muutos_laj char(3), Alkupäivä date, Loppupäivä date, Voi_massa_ number(2,0), Lisäyspäiv date, Sijaintiki number(15,0), Kiinteistö char(24), Muuttuvan_ number(15,0), Tarkis_tus char(2), Raken_nus_ number(4,0), Kiinteis00 char(254), Posti_nume number(6,0), Valmistumi date, Rak_luvan_ date, Poik_keus_ number(2,0), Tieto_lähd number(2,0), Perus_para number(2,0), Perus_pa00 date, Kaava number(2,0), Hallinta_p number(2,0), Julkisivu_ number(2,0), Kerros_ala number(5,0), Kerrosalan date, Kerros_luk number(2,0), Kerrosluvu date, Koko_naisa number(5,0), Kokonais_a date,
      Huo_neisto char(254), Huoneisto_ char(254), Tilavuus number(6,0), Tilavuuden date, Kellari_al number(5,0), Käytös_säo number(3,0), Käytössä_o date, Käyttö_tar number(4,0), Käyttö_t00 date, Lämmi_tyst number(2,0), Lämmitys_t date, Poltto_ain number(3,0), Polttoaine date, Raken_nusm number(2,0), Rungon_rak number(2,0), Varusteide date, Sähkö number(2,0), Kaasu number(2,0), Viemäri number(2,0), Vesijohto number(2,0), Lämmin_ves number(2,0), Aurinko_pa number(2,0), Hissi number(2,0), Ilmas_toin number(2,0), Saunojen_l number(2,0), Väestö_suo number(3,0), Verkosto_l date, Viemäri_li number(2,0), Vesi_johto number(2,0), Sähkö_liit number(2,0),
      Kaasu_liit char(254), Kaapeli_li number(2,0), Pohjois_ko number(8,0), Itä_koordi number(7,0), Koordi_naa char(2), Asumis_oik char(254), Äänestys_a number(4,0), Äänestys00 number(5,0), Tuleva_kun number(4,0), Tuleva_ään number(5,0), Käyttötark char(9), Rakennus__ number(5,0), Rakennus00 date, Rakennnus_ char(20), id number(20,0), kiinteisto number(20,0), lahdeainei number(20,0), interpoloi number(20,0), kiinteis00 char(200), Tn char(3), Id number(11,0), XI number(10,3), YP number(11,3), Kä char(48), Pa number(5,0), Ke char(11), VTJPRT char(11), VTJXI number(10,3), VTJXP number(11,3), VTJKä char(69),
      VTJPa number(5,0), VTJKe number(2,0), T1 number(2,0), T2 char(254), T3 char(254), T4 char(254), T5 char(254), T6 char(254), Käv char(1), Pav char(254), Kev char(254), _predicate char(254)

Bookmark: VEROTETTAVAT RAKENNUKSET - Esri shape
VEROANALYYSI (writer SHAPE_1)
    attributes: KITU char(17), RAKNRO number(4,0), KIITUN number(14,0), RAKTUN number(18,0), RAKNRO_PYS char(10), MALA number(4,0), RAKOSA number(2,0), RAKOSATYYP char(15), ALKUPVM number(8,0), VALMISPVM number(8,0), RAKOSAPA number(8,0), RAKOSATIL number(8,0), KANTARAK char(5), PERUSPARVU number(4,0), IKAVUOSI number(4,0), VKELLARIPA char(8), SAHKOK number(1,0), LAMMITYSK char(10), VESIK char(1), VIEMARIK char(1), TALVIASK char(1), KUISTIPA number(8,0), WCK char(1), SAUNAK char(1), MUOTO char(5), VARASTOPA number(8,0), HISSIK char(1), HISSIPA char(8), ISK char(1), LVK char(1),
      KELLARIPA number(8,0), PALUEPA number(8,0), PTALOKATE char(15), ERISTEK number(2,2), VRKRAKTYYP char(4), KAYTTOTARK char(10), PURKUKUNTO logical, KAYTTOKELV logical, EIKV logical, YLEISHKAYT logical, VEROTUSARV number(13,2), KVRAKENNUS number(13,2), ASTUNNUS char(200), ASNIMI char(200), OMOSUUS char(100), HALOSUUS char(100)

FME custom transformer ListElementExtractor
Extracts one or more consecutive elements in a list and saves their values into regular (non-list) attributes. The range of elements that will be extracted is determined by the starting index and the number of destination attributes which are specified through parameters.
Example 
Assuming that the input feature has a list called "_list{}" which contains five elements [0, 1, 2, 3, 4], this transformer with the following setting extracts the first three elements [0, 1, 2] and saves them into regular attributes called "_first", "_second", and "_third" sequencially.
Source List Attribute: _list{}
Starting Index: 0
Destination Attributes: _first _second _third 
If you set 2 to the "Starting Index", [2, 3, 4] will be extracted. If you set 4 to the "Starting Index", 4 will be extracted and saved into "_first"; "_second" and "_third" will be missing.
Parameters
    Source List Attribute
    :
    Specify a list attribute whose elements should be extracted.
    Starting Index
    :
    Specify the index (0-based) of the first element which you need to start extracting. The index must be an integer greater than or equal to 0. If you set a negative number to this parameter, this transformer considers it as 0.
    Destination Attributes
    :
    Specify one or more attributes which will store the extracted elements, in the order of the elements.
    Lists to Remove
    :
    Optionally you can remove list(s) with specifying through this parameter. This parameter may be useful if you don't need to preserve the source list after extracting its elements.

Parameters:
- LIST_ATTRS =
- NEW_ATTRIBUTES =
- SRC_LIST =
- START_INDEX =

Input (input)
    -> ParameterFetcher
ParameterFetcher
    ATTR_LIST = __lee.src_list {$(SRC_LIST)} __lee.start_index {$(START_INDEX)} __lee.new_attrs {$(NEW_ATTRIBUTES)}
    -> TclCaller
TclCaller
    HIDE_ATTRIBUTES = __lee.new_attrs __lee.src_list __lee.start_index
    NEW_ATTRIBUTES = $(NEW_ATTRIBUTES)
    SRC:
      proc extractElements {} {
          regexp "^(.+)\{\}(\\.\[^\{\}\]+)?$" [FME_GetAttribute "__lee.src_list"] m prefix suffix
          set i [FME_GetAttribute "__lee.start_index"]
          if {$i < 0} {
              set i 0
          }
          foreach attr [FME_GetAttribute "__lee.new_attrs"] {
              FME_CopyAttribute [FME_DecodeText $attr] "$prefix{$i}$suffix"
              incr i
          }
          FME_Execute RemoveAttributes fme_pcre_match "^__lee\\..+"
      }
    TCLPROG = extractElements
    -> AttributeRemover
AttributeRemover
    LIST_ATTRS = $(LIST_ATTRS)
    -> Output (output)
Output (output)

FME custom transformer kiinteistotunnus_muunto

Parameters:
- KIINTEISTOTUNNUS =
- KTMUOTO =

Kiinteistötunnus (input)
    -> TestFilter
TestFilter
    DEFAULT_VALUE = <UNFILTERED>
    TEST_LIST = "BOOL_OP,OR,COMPOSITE_TEST,""""""1"""""",TEST_CLAUSE,CASE_INSENSITIVE_TEST @Value(kiinteistotunnus) CONTAINS -",@Value(kiinteistotunnus) CONTAINS -
    @Value(kiinteistotunnus) CONTAINS - -> AttributeSplitter
    <UNFILTERED> -> SubstringExtractor
AttributeSplitter
    ATTR_NAME = kiinteistotunnus
    DELIMITER = -
    DROP_EMPTY_PARTS = No
    LIST_NAME = _list
    TRIM_OPTION = Both
    -> ListElementExtractor
ListElementExtractor
    NEW_ATTRIBUTES = kt1 kt2 kt3 kt4
    SRC_LIST = _list{}
    START_INDEX = 0
    -> AttributeTrimmer
SubstringExtractor
    END = 2
    RESULT_ATTR = kt1
    SRC_STRING = @Value(kiinteistotunnus)
    START = 0
    -> SubstringExtractor_2
SubstringExtractor_2
    END = 5
    RESULT_ATTR = kt2
    SRC_STRING = @Value(kiinteistotunnus)
    START = 3
    -> SubstringExtractor_3
SubstringExtractor_3
    END = 9
    RESULT_ATTR = kt3
    SRC_STRING = @Value(kiinteistotunnus)
    START = 6
    -> SubstringExtractor_4
SubstringExtractor_4
    END = 13
    RESULT_ATTR = kt4
    SRC_STRING = @Value(kiinteistotunnus)
    START = 10
    -> AttributeTrimmer
AttributeTrimmer
    SRC_ATTRS = kt3,kt1,kt4,kt2
    TRIM_CHARS = 0
    TRIM_TO_NONE = No
    TRIM_TYPE = Left
    -> Junction
    -> AttributeTrimmer_Output
AttributeTrimmer_Output: Inspector
Junction
    -> TestFilter_2
TestFilter_2
    DEFAULT_VALUE = <UNFILTERED>
    TEST_LIST = "BOOL_OP,OR,COMPOSITE_TEST,""""""1"""""",TEST_CLAUSE,TEST $(KTMUOTO) = 905-0-0-0",905-0-0-0,"BOOL_OP,OR,COMPOSITE_TEST,""""""1"""""",TEST_CLAUSE,TEST $(KTMUOTO) = 905-000-0000-0000",905-000-0000-0000,"BOOL_OP,OR,COMPOSITE_TEST,""""""1"""""",TEST_CLAUSE,TEST $(KTMUOTO) = 90500000000000",90500000000000
    905-0-0-0 -> StringConcatenator_3
    905-000-0000-0000 -> StringFormatter_3
    90500000000000 -> StringFormatter
StringFormatter
    FORMAT = 03s
    SRC_ATTRS = kt1,kt2
    -> StringFormatter_2
StringFormatter_2
    FORMAT = 04s
    SRC_ATTRS = kt3,kt4
    -> StringConcatenator
StringConcatenator
    ACTION = Overwrite Existing Attributes
    ATTRLIST = kiinteistotunnus
    PARM_LINE = @Value(kt1)@Value(kt2)@Value(kt3)@Value(kt4)
    -> Out (output)
StringFormatter_3
    FORMAT = 03s
    SRC_ATTRS = kt1,kt2
    -> StringFormatter_4
StringFormatter_4
    FORMAT = 04s
    SRC_ATTRS = kt3,kt4
    -> StringConcatenator_2
StringConcatenator_2
    ACTION = Overwrite Existing Attributes
    ATTRLIST = kiinteistotunnus
    PARM_LINE = @Value(kt1)-@Value(kt2)-@Value(kt3)-@Value(kt4)
    -> Out (output)
StringConcatenator_3
    ACTION = Overwrite Existing Attributes
    ATTRLIST = kiinteistotunnus
    PARM_LINE = @Value(kt1)-@Value(kt2)-@Value(kt3)-@Value(kt4)
    -> Out (output)
Out (output)
